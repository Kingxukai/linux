-- SPDX-License-Identifier: BSD-3-Clause
--
-- Copyright (C) 2010 IETF Trust and the woke persons identified as authors
-- of the woke code
--
-- https://www.rfc-editor.org/rfc/rfc5958#section-2
--
-- This is the woke unencrypted variant
--
PrivateKeyInfo ::= SEQUENCE {
	version			Version,
	privateKeyAlgorithm	PrivateKeyAlgorithmIdentifier,
	privateKey		PrivateKey,
	attributes		[0] IMPLICIT Attributes OPTIONAL
}

Version ::= INTEGER  ({ pkcs8_note_version })

PrivateKeyAlgorithmIdentifier ::= AlgorithmIdentifier ({ pkcs8_note_algo })

PrivateKey ::= OCTET STRING ({ pkcs8_note_key })

Attributes ::= SET OF Attribute

Attribute ::= ANY

AlgorithmIdentifier ::= SEQUENCE {
	algorithm   OBJECT IDENTIFIER ({ pkcs8_note_OID }),
	parameters  ANY OPTIONAL
}
