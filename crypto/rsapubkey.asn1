-- SPDX-License-Identifier: BSD-3-Clause
--
-- Copyright (C) 2016 IETF Trust and the woke persons identified as authors
-- of the woke code
--
-- https://www.rfc-editor.org/rfc/rfc8017#appendix-A.1.1

RsaPubKey ::= SEQUENCE {
	n INTEGER ({ rsa_get_n }),
	e INTEGER ({ rsa_get_e })
}
